--
-- Common Managed Object Definitions for existing and new generation matrices by 
-- GVG & Thomson Multimedia 
--             
THOMSON-MATRIX-MIB DEFINITIONS ::= BEGIN

	--  Relationship to Other MIBs
	--
	--
	--  The objects defined in this MIB are located under the
	--  private.enterprises subtree as shown below:
	--
	--               iso(1).org(3).dod(6).internet(1)          
	--                            |
	--                         private(4)
	--                            |
	--                       enterprises(1)
	--                            |
	--                        gvg(4947)
	--                            |
	--                   gvgRegistrations(2)
	--                           |
	--			       		gvgRouters(4)
	--
	--
	--  Object Synopsis
	--  
	--
	--  All objects within this MIB are prefixed with the OBJECT
	--  IDENTIFIER "p", where "p" is:
	--
	--  iso(1).org(3).dod(6).internet(1).private(4).enterprises(1).
	--          gvg(4947).gvgRegistrations(2).gvgRouters(4)
	--	
	--  or, 1.3.6.1.4.1.4947.2.4
	-- 
	--  Object Name               Object Id         
	--  ====================      ===========
	--  matrices                    p.2    
	--  mtxNotifyGroup				p.4
	--  mtxSysName					p.2.1
	--  mtxSysDescr					p.2.2
	--  mtxFrameType				p.2.3
	--	mtxInputSignalStatus		p.2.4
	--  mtxOutputSignalStatus		p.2.5
	--  mtxBoardStatus				p.2.6	
	--  mtxFrameTemp				p.2.7
	--  mtxPowerSupplyTable			p.2.8
	--  mtxPowerSupplyEntry			p.2.8.1
	--	  mtxPwrID					p.2.8.1.1
	--	    mtxPwrName				p.2.8.1.2
	--		mtxPwrStatus			p.2.8.1.3
	--		mtxPwrACStatus			p.2.8.1.4
	--		mtxPwrDCStatus			p.2.8.1.5
	--  mtxPwrFanStatus				p.2.8.1.6
	--  mtxRefSignalTable			p.2.9
	--    mtxRefSignalEntry			p.2.9.1
	--	    mtxRefIndex				p.2.9.1.1
	--		mtxRefName				p.2.9.1.2
	--		mtxRefStatus			p.2.9.1.3
	--  mtxFanStatusTable			p.2.10
	--    mtxFanStatusEntry			p.2.10.1
	--		mtxFanId				p.2.10.1.1
	--		mtxFanName				p.2.10.1.2
	--		mtxFanStatus			p.2.10.1.3
	--  mtxControllerStatus			p.2.21
	--	msgClass					p.4.1
	--	msgSeverity					p.4.2
	--	msgBehavior					p.4.3
	--	faultDescriptionString		p.4.4
	--	matrixPowerSupplyError		p.2.11
	--	matrixPowerSupplyNoAC		p.2.12
	--	matrixPowerSupplyNoDC		p.2.13
	--	matrixPowerSupplyFanError	p.2.14
	--	matrixFrameFanError			p.2.15
	--	matrixRefSignalAbsent		p.2.16
	--	matrixInputSignalAbsent		p.2.17
	--	matrixOutputSignalAbsent	p.2.18
	--	matrixBoardFault			p.2.19
	--	matrixTempOutofBound		p.2.20
	--	matrixControllerSwitchOver	p.2.22	
	--	mtxAppSoftVer				p.2.23
	--	mtxBootVer					p.2.24
	--	mtxPartNumber				p.2.25
	--	mtxIpAddr					p.2.26
	--	mtxSubnetMask				p.2.27
	--	mtxGatewayIP				p.2.28
	--	mtxFwVersionTable			p.2.29
	--	  mtxFwVersionEntry			p.2.29.1
	--		mtxFwId					p.2.29.1.1
	--		mtxFwName				p.2.29.1.2
	--		mtxFwVersion			p.2.29.1.3
	--	mtxCpTable					p.2.30
	--	  mtxCpEntry				p.2.30.1
	--		mtxCpId					p.2.30.1.1
	--		mtxCpIpAddress			p.2.30.1.2
	--		mtxCpStatus				p.2.30.1.3
	--		mtxCpType				p.2.30.1.4
	--	mtxIoSignalTable			p.2.31
	--	  mtxIoSignalEntry			p.2.31.1
	--		mtxIndexNo				p.2.31.1.1
	--		mtxConnNo				p.2.31.1.2
	--		mtxIoSigDesc			p.2.31.1.3
	--		mtxOutConnectedTo		p.2.31.1.4
	--	matrixLossOfControlPoint	p.2.32
	--	  
	
	IMPORTS
		MODULE-IDENTITY, OBJECT-IDENTITY, NOTIFICATION-TYPE, OBJECT-TYPE,
		Integer32,IpAddress
			FROM SNMPv2-SMI
		MODULE-COMPLIANCE, OBJECT-GROUP 
			FROM SNMPv2-CONF 
	    gvgElModel, gvgElAssetTag , gvgIoSignalEntry , gvgIoSignalStateChange
			FROM GVG-ELEMENT-MIB		
		gvgRegistrations, gvgRouters
			FROM GVG-REG;
          
	matrices MODULE-IDENTITY
		LAST-UPDATED  "200802201000Z"
		ORGANIZATION "Grass Valley Group Inc."
		CONTACT-INFO
			   "Thomson Grass Valley.
				P.O. Box 1114,
				Grass Valley, CA 95945, USA.
				phone: +1 (530) 478-4148
				email: support@grassvalleygroup.com
				http://www.thomsongrassvalley.com"
	DESCRIPTION
				"This MIB module describes attributes and 
				alarms generated by the Matrix Board. 
		
				Thomson Grass Valley grants vendors, end-users, 
				and other interested parties a non-exclusive 
				license to use this specification in connection 
				with the management of its products.
				Copyright Thomson 2002."      

    REVISION      "200802201000Z"
	DESCRIPTION	  "Added new attributes , tables and notification as described below
					attributes 
						  -- mtxAppSoftVer, mtxBootVer, mtxPartNumber,
						  -- mtxIpAddr, mtxSubnetMask, mtxGatewayIP  
					Tables 
					      -- Firmware Version Information
					      -- Control Point Table 
					      -- Extended  gvgIoSignalTable from Element MIB to cater Matrix needs.
					Notifications
						  -- Io Signal State Change Notification
						  -- Control Point Loss"
				
	
	REVISION      "200710151230Z"
	DESCRIPTION	  "Added new attribute mtxControllerStatus and notification matrixControllerSwitchOver"	
	               	
	REVISION      "200402031100Z"	
	DESCRIPTION	  "Changed notifyGroup to mtxNotifyGroup under gvgRouters.4 "				
	
	REVISION      "200304261530Z"
	DESCRIPTION	  "Added states missing(3) and notApplicable(4) 
				   for following mib attributes
						1. mtxInputSignalStatus
						2. mtxOutputSignalStatus
						3. mtxPwrStatus
						4. mtxFanStatus
						5. mtxRefStatus
				   Added state notApplicable(4) to 
				   		1. mtxBoardStatus				   						   		  						
						2. mtxFrameTemp
				   Note: In order to maintain the uniformity of the enumerated status values
				   		 among the various MIB attributes, the enumeration for mtxBoardStatus and 
				   		 mtxFrameTemp attribute has been changed to ok(1),error(2),notApplicable(4)"
	
	REVISION      "200303031730Z"
	DESCRIPTION	  "Changed mtrxFrameTemp data type to INTEGER and defined size limits for 
					faultDescriptionString"	 				   		 				   		 
	
	REVISION      "200302191400Z"
	DESCRIPTION	  "Added new Traps for InputSignalstatus and OutputSignal status, attributes 
				   for the same, removed boardFaultDescription and SignalFaultDescription,
	               re-arrangement of the tree structure and minor cosmetic changes."				   		 
	
	REVISION      "200302041500Z"
	DESCRIPTION	  "Updated Common matrix mib information with minimal information."
	
	REVISION      "200212151200Z"
	DESCRIPTION	  "Added Common matrix mib information."
	
	REVISION      "200205211245Z"
	DESCRIPTION	  "First draft."            
	::= { gvgRouters 2 }
	
	--
	--  The Element MIB top-level groups
	--

	mtxNotifyGroup	OBJECT IDENTIFIER ::= { gvgRouters 4 }    

	-- Matrix System Information 
 	--
 	-- Sample System information
 	--
 	-- mtxSysName 		 : ConcertoAtNewsRoom
 	-- mtxSysDescr		 : Concerto at FIFA Live News Room
 	-- mtxFrameType		 : Concerto

 	mtxSysName 		OBJECT-TYPE
   		SYNTAX		OCTET STRING (SIZE(0..255))
  		MAX-ACCESS	read-only
  		STATUS		current
  		DESCRIPTION	"This object holds the name of Matrix - preferred to access/assign 
  					the same name as control system refers"
  	::= { matrices	1 }
  	
 	mtxSysDescr		OBJECT-TYPE
   		SYNTAX		OCTET STRING (SIZE(0..255))
  		MAX-ACCESS	read-only
  		STATUS		current
  		DESCRIPTION	"Describes more about the matrix capability and various signal types 
  					 the matrix can handle and gives the presence of matrix location"
  	::= { matrices	2 }
  	
 	mtxFrameType 	 OBJECT-TYPE
   		SYNTAX		 OCTET STRING (SIZE(0..64))
  		MAX-ACCESS	 read-only
  		STATUS		 current
  		DESCRIPTION	 "This object details the type of frame such as AES(NB), WB, Concerto etc.."
 	::= { matrices	3 }
 	
    mtxInputSignalStatus 	 OBJECT-TYPE
    	SYNTAX            	 INTEGER {
					     	  		  ok(1),
					    	  		  error(2),
				    	  		  	  missing(3),
									  notApplicable(4)
					  	     		 }
    	MAX-ACCESS         	   read-only
    	STATUS                 current
    	DESCRIPTION           "This attribute gives the status of all the configured input signals."
    ::= { matrices 4}             
    
    mtxOutputSignalStatus  	   OBJECT-TYPE
    	SYNTAX            	   INTEGER {
					     	  			ok(1),
					    	  			error(2),
					    	  		    missing(3),
									    notApplicable(4)
				  	    	 		   }
    	MAX-ACCESS         	   read-only
    	STATUS                 current
    	DESCRIPTION           "This attribute gives the status of all the configured output signals."
    ::= { matrices 5}             


    mtxBoardStatus   	 OBJECT-TYPE
    	SYNTAX           INTEGER {
					     		  ok(1),
					    		  error(2),
			    		  		  notApplicable(4)
				  		     	 }
    	MAX-ACCESS       read-only
    	STATUS           current
    	DESCRIPTION      "This attribute gives the status of all the Boards."
    ::= { matrices 6}             

    
    -- Frame Temperature
   
   	mtxFrameTemp  	  OBJECT-TYPE
   		SYNTAX        INTEGER {
   								ok(1),
   								error(2),
		    		  		    notApplicable(4)
   							  }
    	MAX-ACCESS    read-only
    	STATUS        current
    	DESCRIPTION   "This attribute give the Current temperature of the matrix frame"
    ::= { matrices 7 }

 	
	--	Power supply  
	-- =========================================================================================
	--  mtxPwrID	mtxPwrName	mtxPwrStatus	mtxPwrACStatus	mtxPwrDCStatus	mtxPwrFanStatus
	-- =========================================================================================
	--	1			PS1			Active			Present			Present			Present
	-- =========================================================================================
	--	2			PS2			missing			missing			missing			missing
	-- =========================================================================================
	--	3			PS3			faulty			missing			missing			missing     
	-- =========================================================================================
	
	mtxPowerSupplyTable 		OBJECT-TYPE
		SYNTAX	SEQUENCE OF 	MtxPowerSupplyEntry
		MAX-ACCESS 				not-accessible
		STATUS					current
		DESCRIPTION				"A table containing Power supply specific information"
	::= { matrices 8}
                        
	mtxPowerSupplyEntry 	OBJECT-TYPE
		SYNTAX				MtxPowerSupplyEntry  
		MAX-ACCESS			not-accessible
		STATUS				current
		DESCRIPTION			"Information about a particular Power Supply"
		INDEX				{mtxPwrID}
	::=	{  mtxPowerSupplyTable 1}   
		
	MtxPowerSupplyEntry	::= SEQUENCE{ mtxPwrID 			Integer32,
									  mtxPwrName		OCTET STRING,
							  		  mtxPwrStatus		INTEGER,									  
							  		  mtxPwrACStatus	INTEGER,
							  		  mtxPwrDCStatus 	INTEGER,
							  		  mtxPwrFanStatus 	INTEGER  }
		
    mtxPwrID	   	   OBJECT-TYPE
    	SYNTAX         Integer32 (1..2147483647)
    	MAX-ACCESS     read-only
    	STATUS         current
    	DESCRIPTION    "Sequence number or ID for the power supply present on frame"
    ::= { mtxPowerSupplyEntry 1}                                      
   
    mtxPwrName  	OBJECT-TYPE
   		SYNTAX     	OCTET STRING (SIZE(0..64))
    	MAX-ACCESS  read-only
    	STATUS      current
    	DESCRIPTION "Name of the power supply. For example PS1, PS2 etc.,"
    ::= { mtxPowerSupplyEntry 2}
    
  	mtxPwrStatus	 OBJECT-TYPE
   		SYNTAX     	 INTEGER {
					     	  active(1),
					    	  faulty(2),
					    	  missing(3),
				    		  notApplicable(4)
					  	     }
    	MAX-ACCESS  read-only
    	STATUS      current
    	DESCRIPTION "Gives the current status of power supply on its frame"
    ::= { mtxPowerSupplyEntry 3}
                                                    
  	mtxPwrACStatus		OBJECT-TYPE
   		SYNTAX       	INTEGER{
					    		 active(1),
				    			 faulty(2),
					    	 	 missing(3),
					    	 	 notApplicable(4) 
				  			   }
    	MAX-ACCESS   	read-only
    	STATUS       	current
    	DESCRIPTION  	"Gives the Current status of AC input on this power supply module.
    					 Not applicable case will be sent when there is no AC status is 
    					 supported by the matrix. In the case of Concerto we will not be
    					 able to find the AC input status to the power supply."    
    ::= { mtxPowerSupplyEntry 4}

  	mtxPwrDCStatus  	OBJECT-TYPE
   		SYNTAX       	INTEGER{
					    		 active(1),
					    		 faulty(2),
					    	 	 missing(3),
				    		 	 notApplicable(4) 
				    		   }
    	MAX-ACCESS   	read-only
    	STATUS       	current
    	DESCRIPTION  	"Gives the Current status of DC output from the power supply module.
    					 Not applicable case will be sent when there is no DC status is 
	    				 supported by the matrix. In the case of Concerto we will not be
    					 able to find the DC output status to the power supply."
    ::= { mtxPowerSupplyEntry 5}
                                                    
  	mtxPwrFanStatus 	OBJECT-TYPE
   		SYNTAX        	INTEGER{
					    	  	active(1),
					    	  	faulty(2),
					    	  	missing(3),
				    		  	notApplicable(4)
					  		 	}
    	MAX-ACCESS    	read-only
    	STATUS        	current
    	DESCRIPTION   	"Current status of Fan on this power supply module"
    ::= { mtxPowerSupplyEntry 6}
                                 
	-- Reference Signals 
	-- =================================================
	--  mtxRefIndex		mtxRefName  	mtxRefStatus                                    
	-- =================================================
	--	1				 VID			Present
	-- =================================================
	--	2				 AES1			Missing
	-- =================================================
	--	3				 AES2			Present                     
	-- =================================================
	--	4				 VREF1			Present                     
	-- =================================================
	--	5				 VREF2			Missing                     
	-- =================================================
	--	6				 TimeCode		Present                     
	-- =================================================

	mtxRefSignalTable 		OBJECT-TYPE
		SYNTAX	SEQUENCE OF MtxRefSignalEntry
		MAX-ACCESS 			not-accessible
		STATUS				current
		DESCRIPTION			"A table contains the details about the reference signal supported by the matrices."
	::= { matrices 9}
                        
	mtxRefSignalEntry 	  OBJECT-TYPE
		SYNTAX			  MtxRefSignalEntry
		MAX-ACCESS 		  not-accessible
		STATUS			  current
		DESCRIPTION		  "Information about a particular reference signal "
		INDEX			  {mtxRefIndex}
	::=	{  mtxRefSignalTable 1}   
		
	MtxRefSignalEntry		::= SEQUENCE{ mtxRefIndex	Integer32,   
									      mtxRefName	OCTET STRING,
							  	  	      mtxRefStatus	INTEGER}		
    mtxRefIndex	   	   OBJECT-TYPE
    	SYNTAX         Integer32 (1..2147483647)
    	MAX-ACCESS     read-only
    	STATUS         current
    	DESCRIPTION    "Reference signal Index."
    ::= { mtxRefSignalEntry 1}        
    
    mtxRefName	   	   OBJECT-TYPE
    	SYNTAX         OCTET STRING  (SIZE(0..64))
    	MAX-ACCESS     read-only
    	STATUS         current
    	DESCRIPTION    "Reference signal name - such as VID/AES1/AES2."
    ::= { mtxRefSignalEntry 2}

    mtxRefStatus   	   OBJECT-TYPE
    	SYNTAX         INTEGER {
    							present(1), 
    							faulty(2),
    							missing(3),
    							notApplicable(4)
	    					   }
    	MAX-ACCESS     read-only
    	STATUS         current
    	DESCRIPTION    "Reference signal status - such as Present/Not Present"
    ::= { mtxRefSignalEntry 3}          
    
    -- Fan Status                                   
	-- =================================================
    --  mtxFanId	mtxFanName	mtxFanStatus 
	-- =================================================
	--		1		Left Fan         Running
	-- =================================================
	--		2		Right Fan        Halted
	-- =================================================
	
	mtxFanStatusTable 		OBJECT-TYPE    
		SYNTAX	SEQUENCE OF MtxFanStatusEntry
		MAX-ACCESS 			not-accessible
		STATUS				current
		DESCRIPTION			"This table contains detailed information about each fan present in 
					 		 the matrix."
	::= { matrices 10}
                        
	mtxFanStatusEntry 	  OBJECT-TYPE
		SYNTAX			  MtxFanStatusEntry
		MAX-ACCESS 		  not-accessible
		STATUS			  current
		DESCRIPTION		  "Information about the status of a particular Fan."
		INDEX			  {mtxFanId }
	::=	{  mtxFanStatusTable 1}   
		
	MtxFanStatusEntry	::= SEQUENCE{ mtxFanId 	 	Integer32,
								  	  mtxFanName    OCTET STRING,
								  	  mtxFanStatus  INTEGER   }		
    mtxFanId 		OBJECT-TYPE
    	SYNTAX      Integer32 (1..2147483647)
    	MAX-ACCESS  read-only
    	STATUS      current
    	DESCRIPTION "Fan number"
    ::= { mtxFanStatusEntry 1}    
    
    mtxFanName		OBJECT-TYPE
    	SYNTAX      OCTET STRING  (SIZE(0..64))
    	MAX-ACCESS  read-only
    	STATUS      current
    	DESCRIPTION "This attribute gives the Name of the Fan such as PS1 , PS2"
    ::= { mtxFanStatusEntry 2}

   	mtxFanStatus   	   OBJECT-TYPE
   		SYNTAX         INTEGER{
					    		running(1),
					      		halted(2),
					      		missing(3),  
				    	  		notApplicable(4)
					  	      }
    	MAX-ACCESS     read-only
    	STATUS         current
    	DESCRIPTION    "Current status of Fan such as running or halted "
    ::= { mtxFanStatusEntry 3 }    
    
    mtxControllerStatus   	  OBJECT-TYPE
   		SYNTAX         		  INTEGER{
					    			active(1),
					      			inActive(2),
				    	  			unknown(3),  
					      			notSupported(4)
				  	    	  		}
    	MAX-ACCESS     read-only
    	STATUS         current
    	DESCRIPTION    "Current status of the matrix controller"
    ::= { matrices 21 }    
    
	-- Notification parameters used by Matrix                                  	
	
	msgClass		OBJECT-TYPE
    	SYNTAX      INTEGER{
        	                communication(1),
            	            equipment(2),
                	        environment(3),
                    	    processing(4)
		                  	}
    	MAX-ACCESS  read-only
    	STATUS      current
    	DESCRIPTION "This attribute gives the message class type of an alarm, suppose if an
       				 alarm is of type communication ,then it gives the message class as 
       				 communication "
    ::= { mtxNotifyGroup 1}        

    msgSeverity 	OBJECT-TYPE
    	SYNTAX      INTEGER{
        	                 major(1),
	                         minor(2),
	  						 warning(3),
    	                     critical(4),
        	                 information(5),
				 			 indeterminant(6),
			 				 cleared(7)
	    	                }
    	MAX-ACCESS  read-only
    	STATUS      current
    	DESCRIPTION "This attribute gives the message Severity of an alarm such as major/minor etc.,"
    ::= { mtxNotifyGroup 2}

    msgBehavior		OBJECT-TYPE
    	SYNTAX      INTEGER{        
							 clearedbyuser(1),
            	             clearedbysystem(2),
			    	     	 notpending(3)                                        
	                        }
    	MAX-ACCESS  read-only
   		STATUS      current
		DESCRIPTION "This attribute gives the message Behavior of an alarm."
    ::= { mtxNotifyGroup 3}

    faultDescriptionString   	 OBJECT-TYPE
    	SYNTAX             		 OCTET STRING  (SIZE(0..255))
    	MAX-ACCESS         		 read-only
    	STATUS                   current
    	DESCRIPTION              "This attribute gives the description of an alarm."
    ::= { mtxNotifyGroup 4}             

    
    -- Notification (Alarms) generated by a Matrix

	matrixPowerSupplyError		NOTIFICATION-TYPE
    	OBJECTS         
		{                      
			mtxSysName,
			mtxPwrID,
			mtxPwrName,
			mtxPwrStatus, 
			msgClass,
			msgSeverity,
			msgBehavior,
			faultDescriptionString
		}
    	STATUS          current
    	DESCRIPTION     "This alarm will be generated when  
						 there is an error in power supply module "
    ::= { matrices 11 }

	matrixPowerSupplyNoAC 		NOTIFICATION-TYPE
    	OBJECTS         
		{
			mtxSysName,
			mtxPwrID,
			mtxPwrName,		
			msgClass,
			msgSeverity,
			msgBehavior,
			faultDescriptionString		
		}
    	STATUS          current
    	DESCRIPTION     "This alarm will be generated when there is no AC input to the  
						 power supply module"
    ::= { matrices 12 }
                               
	matrixPowerSupplyNoDC 		NOTIFICATION-TYPE
    	OBJECTS         
		{
			mtxSysName,
			mtxPwrID,
			mtxPwrName,    		
			mtxPwrACStatus,		
			msgClass,
			msgSeverity,
			msgBehavior,
			faultDescriptionString
		}
    	STATUS          current
    	DESCRIPTION     "This alarm will be generated when there is a No DC
						 output from the power supply module"
    ::= { matrices 13 }
    
   	matrixPowerSupplyFanError	NOTIFICATION-TYPE
    	OBJECTS         
		{
			mtxSysName,
			mtxPwrID,		
			mtxPwrName,
			mtxPwrACStatus,
			mtxPwrDCStatus,
			msgClass,
			msgSeverity,
			msgBehavior,
			faultDescriptionString
		}
    	STATUS          current
    	DESCRIPTION     "This alarm will be generated when the matrix frame 
    					  fan is not working."
   ::= { matrices 14 }                           
   
	matrixFrameFanError	NOTIFICATION-TYPE
    	OBJECTS         
		{
			mtxSysName,
			mtxFanId,		
			mtxFanName,
			msgClass,
			msgSeverity,
			msgBehavior,
			faultDescriptionString
		}
    	STATUS          current
    	DESCRIPTION     "This alarm will be generated when the matrix frame 
    					  fan is not working."
   ::= { matrices 15 }
            
   	matrixRefSignalAbsent	NOTIFICATION-TYPE
    	OBJECTS         
		{
			mtxSysName,
			mtxRefIndex,
			mtxRefName,
			msgClass,
			msgSeverity,
			msgBehavior,
			faultDescriptionString		
		}
    	STATUS          current
    	DESCRIPTION     "This alarm will be generated when there is any fault in any reference. "
    ::= { matrices 16 }

	matrixInputSignalAbsent	NOTIFICATION-TYPE
    	OBJECTS         
		{
			mtxSysName,
			mtxInputSignalStatus,
			msgClass,
			msgSeverity,
			msgBehavior,
			faultDescriptionString		
		}
    	STATUS          current
    	DESCRIPTION     "This alarm will be generated when there is any fault in any Input signal. "
    ::= { matrices 17 }


	matrixOutputSignalAbsent	NOTIFICATION-TYPE
    	OBJECTS         
		{
			mtxSysName,
			mtxOutputSignalStatus,
			msgClass,
			msgSeverity,
			msgBehavior,
			faultDescriptionString		
		}
    	STATUS          current
    	DESCRIPTION     "This alarm will be generated when there is any fault in any Output signal. "
    ::= { matrices 18 }

	matrixBoardFault	NOTIFICATION-TYPE
    	OBJECTS         
		{
			mtxSysName,
			mtxBoardStatus,  
			msgClass,
			msgSeverity,
			msgBehavior,
			faultDescriptionString		
		}
    	STATUS          current
    	DESCRIPTION     "This alarm will be generated when there is any fault in any board. "
    ::= { matrices 19 }

	matrixTempOutofBound	NOTIFICATION-TYPE
    	OBJECTS         
		{
			mtxSysName,
			mtxFrameTemp,
			msgClass,
			msgSeverity,
			msgBehavior,
			faultDescriptionString		
		}
    	STATUS          current
    	DESCRIPTION     "This alarm will be generated when matrix temperature goes
    					 out of bound. "
    ::= { matrices 20 }

	matrixControllerSwitchOver	NOTIFICATION-TYPE
    	OBJECTS         
		{
			mtxSysName,
			mtxControllerStatus,
			msgClass,
			msgSeverity,
			msgBehavior,
			faultDescriptionString		
		}
    	STATUS          current
    	DESCRIPTION     "This alarm will be generated when matrix controller changes
    					its state from Active to Inactive and vice versa."
    ::= { matrices 22 }   
    
	
	-- Matrix Application Information 
 	--
 	mtxAppSoftVer 	OBJECT-TYPE
   		SYNTAX		OCTET STRING (SIZE(0..255))
  		MAX-ACCESS	read-only
  		STATUS		current
  		DESCRIPTION	"This object holds the application software version of Matrix."
  	::= { matrices	23 }

 	mtxBootVer 		OBJECT-TYPE
   		SYNTAX		OCTET STRING (SIZE(0..255))
  		MAX-ACCESS	read-only
  		STATUS		current
  		DESCRIPTION	"This object holds the boot software version of Matrix."
  	::= { matrices	24 }     

  	mtxPartNumber	OBJECT-TYPE
   		SYNTAX		OCTET STRING (SIZE(0..255))
  		MAX-ACCESS	read-only
  		STATUS		current
  		DESCRIPTION	"This object holds the part number of Matrix."
  	::= { matrices	25 }       
  	
  	mtxIpAddr		 	OBJECT-TYPE
    	SYNTAX          IpAddress
    	MAX-ACCESS      read-only
    	STATUS          current
    	DESCRIPTION     "This attribute gives the IP address of the Matrix."
    ::= { matrices 26} 

    mtxSubnetMask	 	OBJECT-TYPE
    	SYNTAX          IpAddress
    	MAX-ACCESS      read-only
    	STATUS          current
    	DESCRIPTION     "This attribute gives the Subnet Mask of the Matrix."
    ::= { matrices 27} 
    
    mtxGatewayIP	 	OBJECT-TYPE
    	SYNTAX          IpAddress
    	MAX-ACCESS      read-only
    	STATUS          current
    	DESCRIPTION     "This attribute gives the Gateway IP address of the Matrix."
    ::= { matrices 28} 

     
    -- Firmware Version Status
	-- ===============================================
	--  mtxFWId		mtxFWName			mtxFWVersion 
	-- ===============================================
	--		1		Audio Matrix		V1.0.0
	-- ===============================================
	--		2		Video Matrix       	V1.1.0
	-- ===============================================
	--		3		Medic       		V2.0.0
	-- ===============================================
	
	mtxFwVersionTable 		OBJECT-TYPE    
		SYNTAX	SEQUENCE OF MtxFwVersionEntry
		MAX-ACCESS 			not-accessible
		STATUS				current
		DESCRIPTION			"A list that contains detailed version information of each Firmware available 
							in the matrix."
	::= { matrices 29}
                        
	mtxFwVersionEntry OBJECT-TYPE
		SYNTAX		  MtxFwVersionEntry
		MAX-ACCESS 	  not-accessible
		STATUS		  current
		DESCRIPTION	  "A Firmware version entry."
		INDEX		  { mtxFwId }
	::=	{  mtxFwVersionTable 1}   
		
	MtxFwVersionEntry	::= SEQUENCE{ mtxFwId 	 	Integer32,
								  	  mtxFwName    	OCTET STRING,
								  	  mtxFwVersion  OCTET STRING}		
    mtxFwId 		OBJECT-TYPE
    	SYNTAX      Integer32 (1..2147483647)
    	MAX-ACCESS  read-only
    	STATUS      current
    	DESCRIPTION "A unique value that identifies the each firmware version information."
    ::= { mtxFwVersionEntry 1}    
    
    mtxFwName		OBJECT-TYPE
    	SYNTAX      OCTET STRING  (SIZE(0..64))
    	MAX-ACCESS  read-only
    	STATUS      current
    	DESCRIPTION "This attribute gives the Name of the Firmware such as Audio Matrix, Video Matrix."
    ::= { mtxFwVersionEntry 2}     
    
    mtxFwVersion	OBJECT-TYPE
    	SYNTAX      OCTET STRING  (SIZE(0..64))
    	MAX-ACCESS  read-only
    	STATUS      current
    	DESCRIPTION "This attribute gives the Version information of each Firmware present in the matrix."
    ::= { mtxFwVersionEntry 3}
    
    
    -- Matrix Control Point Information
	-- ============================================================================
	--  mtxCpId		mtxCpIpAddress				mtxCpStatus		mtxCpType
	-- ============================================================================
	--		1			  192.168.1.100			 active			Controller		
	-- ============================================================================
	--		2			  192.168.1.102			 faulty			Controller		
	-- ============================================================================
	--		3			  192.168.1.110			 active			NP Client		
	-- ============================================================================
	
	mtxCpTable 		OBJECT-TYPE    
		SYNTAX	SEQUENCE OF MtxCpEntry
		MAX-ACCESS 			not-accessible
		STATUS				current
		DESCRIPTION			"A list that contains control point that is connected to matrix."
	::= { matrices 30}
                        
	mtxCpEntry OBJECT-TYPE
		SYNTAX		  MtxCpEntry
		MAX-ACCESS 	  not-accessible
		STATUS		  current
		DESCRIPTION	  "A Control Point entry."
		INDEX		  {mtxCpId }
	::=	{  mtxCpTable 1}   
		
	MtxCpEntry	::= SEQUENCE{ mtxCpId 	 		Integer32,
							  mtxCpIpAddress   	IpAddress,
							  mtxCpStatus  		INTEGER,
							  mtxCpType			OCTET STRING}		
    mtxCpId 		OBJECT-TYPE
    	SYNTAX      Integer32 (1..2147483647)
    	MAX-ACCESS  read-only
    	STATUS      current
    	DESCRIPTION "A unique value that identifies the each control point."
    ::= { mtxCpEntry 1}    

  	mtxCpIpAddress	 	OBJECT-TYPE
    	SYNTAX          IpAddress
    	MAX-ACCESS      read-only
    	STATUS          current
    	DESCRIPTION     "This attribute gives the IP address of the Control Point."
    ::= { mtxCpEntry 2}    
    
    mtxCpStatus	OBJECT-TYPE
    	SYNTAX     	INTEGER{        
				   	  		active(1),
				  	  		faulty(2),
				   	  		missing(3),
				   	  		notApplicable(4)
                   		   }
    	MAX-ACCESS 	read-only
    	STATUS     	current
    	DESCRIPTION	"This attribute gives the Control Point Status"
    ::= { mtxCpEntry 3}

     mtxCpType		OBJECT-TYPE
    	SYNTAX      OCTET STRING  (SIZE(0..64))
    	MAX-ACCESS  read-only
    	STATUS      current
    	DESCRIPTION "This attribute gives the type of the control point such as Controller or NP Client."
    ::= { mtxCpEntry 4}     

    
    
   	-- Extending gvgIOSignal Table for Matrix specific         
    -- ===============================================================
	--  mtxIndexNo	mtxConnNo	mtxIoSigDesc	mtxOutConnectedTo   
    -- ===============================================================
    --    1            1         AES Signal          -1
    -- ===============================================================
 	--    1            2         AES Signal		     -1
    -- ===============================================================
    --    1            3         SD Signal    	     -1
    -- ===============================================================
    --    1            1         SD Signal	          8
    -- ===============================================================
    --    2            2         HD Signal  	      6
    -- ===============================================================
	--    2            3         AES Signal  	      2
    -- ===============================================================
    
    --  1st example in above table describes - Logical matrix index no.1 and input connector no.1 contains AES signal 
    --  and last column contains -1, that is this row contains the Input signal information and this will not be contained
    --  any output connector number information
    
    -- Last example in above table describes - Logical matrix index no.2 and output connector no.3 contains AES signal 
    -- and last column contains 21, that is this row contains the Input signal connector number connected to output 
    -- connector no.2
           
           
	mtxIoSignalTable 	OBJECT-TYPE    
		SYNTAX	SEQUENCE OF MtxIoSignalEntry
		MAX-ACCESS 			not-accessible
		STATUS				current
		DESCRIPTION			"A list that contains detailed information about each Input/Output signal of the matrix."
	::= { matrices 31}
                        
	mtxIoSignalEntry   OBJECT-TYPE
		SYNTAX			  MtxIoSignalEntry
		MAX-ACCESS 		  not-accessible
		STATUS			  current
		DESCRIPTION		  "Additional objects for a gvgIoSignalEntry."
		AUGMENTS		 { gvgIoSignalEntry }
	::=	{  mtxIoSignalTable 1}   

	MtxIoSignalEntry	::= SEQUENCE{ mtxIndexNo 	 	Integer32,
									  mtxConnNo			Integer32,
									  mtxIoSigDesc    	OCTET STRING,
									  mtxOutConnectedTo	Integer32 }		
    
    mtxIndexNo 			OBJECT-TYPE
    	SYNTAX      	Integer32
    	MAX-ACCESS  	read-only
    	STATUS      	current
    	DESCRIPTION 	"This is an Matrix index number. Entire physical matrix is logically dived into logical matrix
    					 and referred as matrix index number. This is an 1 based value"
    ::= { mtxIoSignalEntry 1}    

    mtxConnNo 			OBJECT-TYPE
    	SYNTAX      	Integer32
    	MAX-ACCESS  	read-only
    	STATUS      	current
    	DESCRIPTION 	"Matrix connector number."
    ::= { mtxIoSignalEntry 2}    

     mtxIoSigDesc		OBJECT-TYPE
    	SYNTAX      	OCTET STRING  (SIZE(0..64))
    	MAX-ACCESS  	read-only
    	STATUS      	current
    	DESCRIPTION 	"This attribute gives the IO Signal description, such as AES Signal/SD Signal etc."
    ::= { mtxIoSignalEntry 3}        

    mtxOutConnectedTo 	OBJECT-TYPE
    	SYNTAX      	Integer32
    	MAX-ACCESS  	read-only
    	STATUS      	current
    	DESCRIPTION 	"Matrix Input connector number that is currently connected to output. 
    					 If the signal is in question is input signal , then this value will be -1."
    ::= { mtxIoSignalEntry 4}    

   
   -- Notification description  
  	matrixLossOfControlPoint		NOTIFICATION-TYPE
        OBJECTS         
		{
			mtxCpId,
			msgClass,
			msgSeverity,
			msgBehavior,
			faultDescriptionString
		}
        STATUS          current
        DESCRIPTION     "This alarm is generated whenever matrix detects it lost its control point, 
                         This error trap shall be cleared once control point reconnects back."
        ::= { matrices 32 }

END
